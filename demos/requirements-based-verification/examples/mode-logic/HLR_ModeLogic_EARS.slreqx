# HLR_ModeLogic_EARS

## 16: Establish Communications (Container)

### 17: Enter Establish Communications at Power Up (Functional)
When the flight control system powers up, the system shall enter the Establish Communications mode.

### 18: Enter Establish Communications from Crash (Functional)
When the system is in crash mode, the system shall enter the Establish Communications mode.

### 19: Enter Establish Communications from Land (Functional)
When the system is in Land mode and the quadcopter's roll angle is less than 5 degrees, pitch angle is less than 5 degrees, and vertical velocity is less than 0.1 m/s, the system shall enter the Establish Communications mode.

## 25: Calibrate the Sensors (Container)

### 26: Enter Calibrate Sensors from Initialization (Functional)
When the system is in Initialization mode and the ground station issues a calibration command, the system shall enter the Calibrate Sensors mode.

### 27: Enter Calibrate Sensors from Ready for Flight (Functional)
When the system is in Ready for Flight mode and the ground station issues a calibration command, the system shall enter the Calibrate Sensors mode.
